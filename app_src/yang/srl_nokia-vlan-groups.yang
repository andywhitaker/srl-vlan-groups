module srl_nokia-vlan-groups {
  yang-version 1.1;
  namespace "urn:nokia.com:srlinux:vlan-groups:vlan-groups";
  prefix srl_nokia-vlan-groups;

  import srl_nokia-common {
    prefix srl_nokia-comm;
  }
  import srl_nokia-interfaces {
    prefix srl_nokia-if;
  }

  description
    "YANG model for Nokia SR Linux VLAN Groups NDK application.";

  revision 2024-08-01 {
    description "Update state hierarchy";
  }

  revision 2024-03-05 {
    description "Initial revision";
  }

  container vlan-groups {
    description "Top level container for VLAN groups";

    list vlan-group {
      key "name";
      description "A VLAN group";

      leaf name {
        type string {
          length "1..255";
        }
        description "Name of the VLAN group";
      }

      container applied {
        config false;
        description "State relating to applied interfaces";

        container interfaces {
          description "Applied interfaces container";

          list interface {
            key "name";
            description "List of interfaces this VLAN group is applied to";

            leaf name {
              type string;
              description "Interface name";
            }
          }
        }
      }

      container created {
        config false;
        description "State relating to created entities";

        container network-instances {
          description "Created network-instances container";

          list network-instance {
            key "name";
            description "List of network instances created by this VLAN group";

            leaf name {
              type string;
              description "Network instance name";
            }
          }
        }
      }

      list tag {
        key "vlan-id";
        description "List of tagged VLAN configurations";

        leaf vlan-id {
          type srl_nokia-comm:vlan-id;
          description "VLAN ID";
        }

        leaf subinterface-id {
          type uint32 {
            range "0..9999";
          }
          description "Subinterface ID to use for this VLAN. Defaults to the VLAN ID if not provided.";
        }

        leaf mac-vrf {
          type string {
            length "1..255";
          }
          description "Name of the MAC-VRF to associate with this subinterface. Defaults to vlan-<vlan-id> if not provided.";
        }
      }

      container untagged {
        presence "Enable untagged VLAN configuration";
        description "Untagged VLAN configuration";

        leaf subinterface-id {
          type uint32 {
            range "0..9999";
          }
          default 1;
          description "Subinterface ID to use for the untagged traffic. Defaults to 1 if not provided.";
        }

        leaf mac-vrf {
          type string {
            length "1..255";
          }
          default "vlan-1";
          description "Name of the MAC-VRF to associate with the untagged subinterface. Defaults to vlan-1 if not provided.";
        }
      }
    }
  }

  augment "/srl_nokia-if:interface" {
    container vlan-groups {
      description "VLAN group configuration applied to this interface";

      list vlan-group {
        key "name";
        description "VLAN group applied to this interface";

        leaf name {
          type leafref {
            path "/srl_nokia-vlan-groups:vlan-groups/srl_nokia-vlan-groups:vlan-group/srl_nokia-vlan-groups:name";
          }
          description "Name of the VLAN group";
        }

        container created {
          config false;
          description "State relating to created subinterfaces";

          list subinterface {
            key "index";
            description "List of subinterfaces created by this VLAN group";

            leaf index {
              type uint32 {
                range "0..9999";
              }
              description "Subinterface index";
            }

            leaf associated-mac-vrf {
              type string;
              description "The network-instance this subinterface is bound to";
            }
          }
        }
      }
    }
  }
}
